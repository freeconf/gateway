module fc-gateway {

    revision 0;   

    grouping deviceHnd {
        leaf deviceId {
            type string;
        }

        leaf address {
            type string;
        }        
    }

    list registration {
        key "deviceId";
        config false;
        uses deviceHnd;
    }

    notification update {
        uses deviceHnd;
    }
}
